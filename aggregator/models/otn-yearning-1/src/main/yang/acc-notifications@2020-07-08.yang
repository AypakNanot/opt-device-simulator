module "acc-notifications" {
  yang-version "1.1";
  namespace "urn:ccsa:yang:acc-notifications";
  prefix "acc-ntf";
  revision "2020-07-08" {
    description
      "Final revision.";
    reference
      "CCSA：接入型OTN管控技术要求";
  }

  typedef "event-type" {
    type "enumeration" {
      enum "object-creation" {
        value "0";
      }

      enum "object-deletion" {
        value "1";
      }

      enum "attribute-value-change" {
        value "2";
      }

    }

  }

  grouping "event" {
    leaf "event-serial-no" {
      mandatory "true";
      type "uint64";
    }

    leaf "event-type" {
      mandatory "true";
      type "event-type";
    }

    leaf "object-name" {
      mandatory "true";
      type "string";
    }

    leaf "object-type" {
      mandatory "true";
      type "string";
    }

  }

  notification "common-notification" {
    container "event" {
      uses "event";
    }

  }

  notification "attribute-value-change-notification" {
    container "event" {
      uses "event";
    }

    container "attribute-value-change" {
      leaf "attribute-name" {
        mandatory "true";
        type "string";
      }

      leaf "new-value" {
        mandatory "true";
        type "string";
      }

      leaf "old-value" {
        type "string";
      }

    }

  }

}
