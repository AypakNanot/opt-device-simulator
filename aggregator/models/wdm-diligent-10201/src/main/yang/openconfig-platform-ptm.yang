module openconfig-platform-ptm {

  yang-version "1";

  // namespace
  namespace "http://openconfig.net/yang/platform/ptm";

  prefix "oc-ptm";

  import openconfig-platform { prefix oc-platform;revision-date "2020-06-30"; }
  import openconfig-platform-types { prefix oc-platform-types;revision-date "2020-06-30"; }
  import openconfig-extensions { prefix oc-ext;revision-date "2018-10-17"; }


  // meta
  organization " working group";

  contact
    "  working group";

  description
    "This module defines data related to ptm components in
    the openconfig-platform model";

  oc-ext:openconfig-version "0.1.0";
 
  revision "2020-06-30" {
    description
      "Initial revision";
    reference "0.1.0";
  }


  grouping ptm-config {
    description
      "Configuration data for ptm components";   
    leaf work-state  {
      type oc-platform-types:ptm-work-type;
      description
         "Available memory for ptm components";
    }   
    
  }

  grouping ptm-state {
    description
      "Operational state data for mux components";
      uses ptm-config;
  }

  

  // data definition statements

  // augment statements
 
  augment "/oc-platform:components/oc-platform:component/oc-platform:ptm/oc-platform:state" {
    description
      "Adding ptm state data";

    uses ptm-state;
  }
  augment "/oc-platform:components/oc-platform:component/oc-platform:ptm/oc-platform:config" {
    description
      "Adding ptm config data";

    uses ptm-config;
  }

  // rpc statements
  
  // notification statements

}
