module openconfig-platform-foadm {

  yang-version "1";

  // namespace
  namespace "http://openconfig.net/yang/platform/foadm";

  prefix "oc-foadm";

  import openconfig-platform { prefix oc-platform;revision-date "2020-06-30"; }
  import openconfig-extensions { prefix oc-ext;revision-date "2018-10-17"; }
  import openconfig-platform-types { prefix oc-platform-types;revision-date "2020-06-30"; }
  import openconfig-transport-types { prefix oc-opt-types;revision-date "2020-06-30"; }


  // meta
  organization "OpenConfig working group";

  contact
    "OpenConfig working group
    www.openconfig.net";

  description
    "This module defines data related to foadm components in the
    OpenConfig platform model.";

  oc-ext:openconfig-version "0.1.1";


  revision "2020-06-30" {
    description
      "Initial revision";
    reference "0.1.0";
  }

  // OpenConfig specific extensions for module metadata.
  oc-ext:regexp-posix;
  oc-ext:catalog-organization "openconfig";
  oc-ext:origin "openconfig";

  // identity statements

  // typedef statements

  // grouping statements
  grouping media-channel-spectrum-state {
    description
      "Operational state data for the media channel";

    leaf lower-frequency {
      type oc-opt-types:frequency-type;
      description
        "Lower frequency of the specified spectrum power";
    }

    leaf upper-frequency {
      type oc-opt-types:frequency-type;
      description
        "Upper frequency of the specified spectrum power";
    } 
  }
  
  grouping add-drop-pac{
    description
      "Add/drop information for foadm components";
    
    leaf add-drop-port {
      type leafref {
        path "/oc-platform:components/oc-platform:component/" +
          "oc-platform:name";
      }
      description
        "Reference to system-supplied name of the wavelength-router
        port component.";
    }       
  }

  grouping foadm-config {
    description
      "Operational config data for foadm components";
  }
  
  grouping foadm-state {
    description
      "Operational state data for foadm components";

    leaf channel-interval {
      type oc-platform-types:channel-interval-type;
      description
        "Sets foadm mode";
    } 
    
    leaf add-drop-channel-num {
      type uint32;
      description
        "Add drop channel number, currently add number should equals 
         drop number, default value is 4";
    }
    
    container frequence-channels{
	    config false;
        list frequence-channel {
            key "lower-frequency upper-frequency";
            uses media-channel-spectrum-state; 
            container add-drop-pac {
              uses add-drop-pac; 
            }
        }
    }
	
	 
  }


  // data definition statements

  // augment statements

  augment "/oc-platform:components/oc-platform:component/" +
    "oc-platform:foadm/oc-platform:state" {
    description
      "Adding foadm data to component model";

    uses foadm-config;
    uses foadm-state;
  }

}
