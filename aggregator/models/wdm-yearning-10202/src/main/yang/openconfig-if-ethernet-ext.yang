module openconfig-if-ethernet-ext {

  yang-version "1";

  // namespace
  namespace "http://openconfig.net/yang/interfaces/ethernet-ext";

  prefix "oc-eth-ext";

  // import some basic types
  import openconfig-interfaces { prefix oc-if;revision-date "2019-11-19"; }
  import openconfig-if-ethernet { prefix oc-eth;revision-date "2023-04-26"; }
  import openconfig-yang-types { prefix oc-yang;revision-date "2018-11-21"; }
  import openconfig-extensions { prefix oc-ext;revision-date "2018-10-17"; }


  // meta
  organization "OpenConfig working group";

  contact
    "OpenConfig working group
    www.openconfig.net";

  description
    "This module adds extensions to the base ethernet configuration
    and operational state model to support additional use cases.";

  oc-ext:openconfig-version "0.1.1";

  revision "2018-11-21" {
    description
      "Add OpenConfig module metadata extensions.";
    reference "0.1.1";
  }

  revision "2018-07-10" {
    description
      "Initial version of Ethernet extensions module to add frame
      size distribution stats";
    reference "0.1.0";
  }

  // OpenConfig specific extensions for module metadata.
  oc-ext:regexp-posix;
  oc-ext:catalog-organization "openconfig";
  oc-ext:origin "openconfig";

  grouping ethernet-in-frames-size-dist {
    description
      "Grouping for defining the size distribution of the frames
      received";

    container in-distribution {
      description
        "The size distribution of the received frames.";

        leaf in-frames-64-octets {
          type oc-yang:counter64;
          description
            "Number of packets (including bad packets) received that
            were 64 bytes in length (excluding framing bits but
            including FCS bytes).";
        }

        leaf in-frames-65-127-octets {
          type oc-yang:counter64;
          description
            "Number of good and bad packets received that were
            between 65 and 127 bytes in length (excluding framing bits
            but including FCS bytes).";
        }

        leaf in-frames-128-255-octets {
          type oc-yang:counter64;
          description
            "Number of good and bad packets received that were
            between 128 and 255 bytes in length inclusive
            (excluding framing bits but including FCS bytes).";
        }

        leaf in-frames-256-511-octets {
          type oc-yang:counter64;
          description
            "Number of good and bad packets received that were
            between 256 and 511 bytes in length inclusive
            (excluding framing bits but including FCS bytes).";
        }

        leaf in-frames-512-1023-octets {
          type oc-yang:counter64;
          description
            "Number of good and bad packets received that were
            between 512 and 1023 bytes in length inclusive
            (excluding framing bits but including FCS bytes).";
        }

        leaf in-frames-1024-1518-octets {
          type oc-yang:counter64;
          description
            "Number of good and bad packets received that were
            between 1024 and 1518 bytes in length inclusive
            (excluding framing bits but including FCS bytes).";
        }
    }
  }

  // augment statements

  augment "/oc-if:interfaces/oc-if:interface/oc-eth:ethernet/" +
    "oc-eth:state/oc-eth:counters" {
      description
        "Adds size distribution to the ethernet counters";

      uses ethernet-in-frames-size-dist;
  }

}
