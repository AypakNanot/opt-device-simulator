module openconfig-event {
    yang-version 1.1;
    namespace "http://openconfig.net/yang/notification";
    prefix ntf;
    import openconfig-types { prefix oc-types;revision-date "2023-04-26"; }

    organization "xxx";
    contact "xxx";
    description "This module defines a YANG data model for use with the
        NETCONF protocol that allows the NETCONF client to
        receive event notifications.";
    revision 2023-04-26 {
        description "Initial revision.";
        reference "RFC xxx";
    }
    /*
    * Common types
    */
    typedef event-type {
        type enumeration {
            enum object-creation {
                value 0;
                description "event-type object-creation";
            }
            enum object-deletion {
                value 1;
                description "event-type object-deletion";
            }
            enum attribute-value-change {
                value 2;
                description "event-type attribute-value-change";
            }
        }
        description "event-type";
    }   
    /*
    * Groupings
    */    
    grouping event {
        leaf event-serial-no {
            type uint64;
            description "event event-serial-no";
        }
        
        leaf time-created {
          type oc-types:timeticks64;
          description
              "The time at which the event was raised by the system.
                This value is expressed as nanoseconds since the Unix Epoch";
        }
        
        leaf object-name {
            type string;
            description "event object-name";
        }
        leaf object-type {
            type oc-types:object-type;
            description "event object-type";
        }
            
        leaf event-type {
            type event-type;
            description "event event-type";
        }
        
        leaf event-abbr {
            type string;
            description "event abbr";
        }
        
        container avc {
            leaf attribute-name {
                type string;
                description "attribute-value-change attribute-name";
            }
            leaf new-attribute-value {
                type string;
                description "attribute-value-change new-attribute-value";
            }
            leaf old-attribute-value {
                type string;
                description "attribute-value-change old-attribute-value";
            }
            description "attribute-value-change";
        }
        description "event";
    }

    /*
    * Notifications
    */    
    notification event-notification {
        container event {
            uses event;
            description "common-notification";
        }
        description "common-notification";
    }
     
}
