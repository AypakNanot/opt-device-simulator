module miniotn-alarms {

  yang-version 1; 

  // namespace
  namespace "urn:cmcc:yang:alarms";

  prefix "mo-alarms";

  // import some basic types
  import openconfig-alarm-types { prefix oc-alarm-types;revision-date "2018-11-21";}
  import openconfig-extensions { prefix oc-ext;revision-date "2018-10-17"; }
  import openconfig-platform { prefix oc-platform; revision-date "2023-04-26"; }
  import ietf-yang-types { prefix yang; }
  import openconfig-types { prefix oc-types;revision-date "2023-04-26"; }
  import miniotn-performance-types {prefix mo-performance-types;revision-date "2023-04-26";}

  // meta
  organization "Cmcc minOTN working group";

  contact
    "";

  description
    "This module defines operational state data related to alarms
    that the device is reporting.

    This model reuses some data items defined in the draft IETF
    YANG Alarm Module:
    https://tools.ietf.org/html/draft-vallin-netmod-alarm-module-02

    Portions of this code were derived from the draft IETF YANG Alarm
    Module. Please reproduce this note if possible.

    IETF code is subject to the following copyright and license:
    Copyright (c) IETF Trust and the persons identified as authors of
    the code.
    All rights reserved.

    Redistribution and use in source and binary forms, with or without
    modification, is permitted pursuant to, and subject to the license
    terms contained in, the Simplified BSD License set forth in
    Section 4.c of the IETF Trust's Legal Provisions Relating
    to IETF Documents (http://trustee.ietf.org/license-info).";

  oc-ext:openconfig-version "0.3.1";

  revision "2023-04-26" {
    description
      "Initial release for MinOTN.";
    reference "1.0.0";
  }

  // OpenConfig specific extensions for module metadata.
  oc-ext:regexp-posix;
  oc-ext:catalog-organization "openconfig";
  oc-ext:origin "openconfig";

  // grouping statements

  grouping alarm {
    description
      "Operational state data for device alarms";

    leaf alarm-serial-no {
        mandatory true;
        type uint64;
        description "alarm alarm-serial-no";
    }
        
         
    leaf alarm-code {
        type string;
        mandatory true;
        description "alarm code";
    }  

    leaf object-name {
        type string {
            length "1..64";
        }
        mandatory true;
        description "alarm object-name";
    }

    leaf object-type {
        type oc-types:object-type;
        mandatory true;
        description "alarm object-type";
    } 

    leaf additional-text {
      type string;
      description
        "The string used to inform operators about the alarm. This
         MUST contain enough information for an operator to be able
         to understand the problem. If this string contains structure,
         this format should be clearly documented for programs to be
         able to parse that information";
      reference
        "IETF YANG Alarm Module: Draft - typedef alarm-text
        https://tools.ietf.org/html/draft-vallin-netmod-alarm-module-02";
    }

    leaf start-time { 
        type yang:date-and-time;
        description "alarm start-time";
    }
    
    leaf end-time {
        type yang:date-and-time;
        description "alarm end-time";
    }

    leaf perceived-severity {
      type identityref {
        base oc-alarm-types:OPENCONFIG_ALARM_SEVERITY;
      } 
      description
        "The severity level indicating the criticality and impact
        of the alarm";
      reference
        "IETF YANG Alarm Module: Draft - typedef severity
        https://tools.ietf.org/html/draft-vallin-netmod-alarm-module-02";
    }

    leaf alarm-state {
        type oc-alarm-types:alarm-state;
        mandatory true;
        description "alarm alarm-state";
    }
  }
  
  grouping alarms-top {
        list alarm {
            key 'alarm-serial-no';
            config false;           
            
            uses alarm;
            description "alarms list";
        }
        description "alarms";
    }
 

   /*
    * the data tree
    */

    container alarms {
        uses alarms-top;
        description "alarms container";
    } 
    
 
    /*
    * notifications
    */
    notification alarm-notification {
        container alarm {
        uses alarm;
        description "alarm-notification container";
    }
    description "alarm-notification";
    }
    
  

  // augments

  augment "/oc-platform:components/oc-platform:component/oc-platform:state" {
    description
      "Adds specific alarms related to a component.";

    leaf equipment-failure {
      type boolean;
      default "false";
      description
        "If true, the hardware indicates that the component's physical equipment
        has failed";
    }

    leaf equipment-mismatch {
      type boolean;
      default "false";
      description
        "If true, the hardware indicates that the component inserted into the
        affected component's physical location is of a different type than what
        is configured";
    }
  }

}
