module openconfig-platform-chassis {

  yang-version "1";

  // namespace
  namespace "http://openconfig.net/yang/platform/chassis";

  prefix "oc-chassis";

  import openconfig-platform { prefix oc-platform;revision-date "2023-04-26"; }
  import openconfig-platform-types { prefix oc-platform-types;revision-date "2023-04-26"; }
  import openconfig-extensions { prefix oc-ext;revision-date "2018-10-17"; }
  import openconfig-types { prefix oc-types;revision-date "2023-04-26"; }


  // meta
  organization " working group";

  contact
    "  working group";

  description
    "This module defines data related to chassis components in
    the openconfig-platform model";

  oc-ext:openconfig-version "0.1.0";

  revision "2020-06-30" {
    description
      "Initial revision";
    reference "1.7.2";
  }

  // extension statements

  // feature statements

  // identity statements

  // typedef statements
    
  // grouping statements

  grouping chassis-config {
    description
      "Configuration data for chassis components";    
      
    leaf lcd  {
      type string;    
      description
         "Sets the lcd content";          
    }
    leaf direction {
      type enumeration {
        enum EAST {
          description
            "EAST ";
        }
        enum WEST {
          description 
            "WEST";
        }
      }
    } 
  }

  grouping chassis-state {
    description
      "Operational state data for chassis components"; 
              
    leaf chassis-type {
      type oc-platform-types:component-chassis-type;    
      description
         "Chassis type for chassis components";       
    }

    leaf remain-power-capacity {
      type decimal64 {
        fraction-digits 2;
      }
      description "Remain power";
    }
  }


  // data definition statements

  // augment statements

  augment "/oc-platform:components/oc-platform:component/oc-platform:chassis/oc-platform:config" {
    description
      "Adding chassis data to physical inventory";

    uses chassis-config;
  }

 augment "/oc-platform:components/oc-platform:component/oc-platform:chassis/oc-platform:state" {
    description
      "Adding chassis state data";

    uses chassis-config;
    uses chassis-state;
  }

  // rpc statements
  
  // notification statements

}
