module openconfig-platform-mcu {

  yang-version "1";

  // namespace
  namespace "http://openconfig.net/yang/platform/mcu";

  prefix "oc-mcu";

  import openconfig-platform { prefix oc-platform;revision-date "2023-04-26"; }
  import openconfig-platform-types { prefix oc-platform-types;revision-date "2023-04-26"; }
  import openconfig-extensions { prefix oc-ext;revision-date "2018-10-17"; }


  // meta
  organization " working group";

  contact
    "  working group";

  description
    "This module defines data related to mcu components in
    the openconfig-platform model";

  oc-ext:openconfig-version "0.1.0";
 
  revision "2023-04-26" {
    description
      "Initial release for MinOTN.";
    reference "1.0.0";
  }

  // extension statements

  // feature statements

  // identity statements

  // typedef statements
    
  // grouping statements

  grouping mcu-config {
    description
      "Configuration data for mcu components";    
    
  }

  grouping mcu-state {
    description
      "Operational state data for mcu components"; 
                
    leaf mcu-total-memory  {
      //TODO: mandatory true;
      type uint32;
      units MB; 
      description
         "total memory for mcu components";
    }     
    
    leaf mcu-available-memory  {
      //TODO: mandatory true;
      type uint32;
      units MB;
      description
         "Available memory for mcu components";
    }
    leaf mcu-cpu-utilization  {
      type uint64;
      description
          "The utilization of Current CPU";
    }
    
    leaf active  {
      //TODO: mandatory true;
      type boolean;
      description
         "Active status for mcu components";
    }
  }

  

  // data definition statements

  // augment statements
 
 augment "/oc-platform:components/oc-platform:component/oc-platform:mcu/oc-platform:state" {
    description
      "Adding mcu state data";

    uses mcu-state;
  }

  // rpc statements
  
  // notification statements

}
