module openconfig-event {

  yang-version "1";

  // namespace
  namespace "http://openconfig.net/yang/event";

  prefix "oc-event";

  // import some basic types
  import openconfig-alarm-types { prefix oc-alarm-types;revision-date "2020-06-30"; }
  import openconfig-extensions { prefix oc-ext;revision-date "2018-10-17"; }
  import openconfig-types { prefix oc-types;revision-date "2020-06-30"; }
  import openconfig-inet-types { prefix oc-inet;revision-date "2019-04-25"; }

   // meta
  organization "private";

  description
    "This YANG module contains all event notification for DCI Box systems.";


  oc-ext:openconfig-version "0.12.2";


  revision "2020-06-30" {
    description
      "Initial release version";
    reference "0.1.0";
  }

  // typedef statements 


 //兼容I型机 上报事件解析找不到 identity
  identity UNKNOWN {
    base oc-alarm-types:OPENCONFIG_ALARM_SEVERITY;
    description
      "Indicates that the severity level could not be determined.
      This level SHOULD be avoided.";
  }

  identity MINOR {
    base oc-alarm-types:OPENCONFIG_ALARM_SEVERITY;
    description
      "Indicates the existence of a non-service affecting fault
      condition and that corrective action should be taken in
      order to prevent a more serious (for example, service
      affecting) fault. Such a severity can be reported, for
      example, when the detected alarm condition is not currently
      degrading the capacity of the resource";
  }

  identity WARNING {
    base oc-alarm-types:OPENCONFIG_ALARM_SEVERITY;
    description
      "Indicates the detection of a potential or impending service
      affecting fault, before any significant effects have been felt.
      Action should be taken to further diagnose (if necessary) and
      correct the problem in order to prevent it from becoming a more
      serious service affecting fault.";
  }

  identity MAJOR {
    base oc-alarm-types:OPENCONFIG_ALARM_SEVERITY;
    description
      "Indicates that a service affecting condition has developed
      and an urgent corrective action is required. Such a severity
      can be reported, for example, when there is a severe
      degradation in the capability of the resource and its full
      capability must be restored.";
  }

  identity CRITICAL {
    base oc-alarm-types:OPENCONFIG_ALARM_SEVERITY;
    description
      "Indicates that a service affecting condition has occurred
      and an immediate corrective action is required. Such a
      severity can be reported, for example, when a resource becomes
      totally out of service and its capability must be restored.";
  }
  grouping event-top {
    description
      "state data for device events";

    leaf id {
      type string;
      description
        "Unique ID for the event -- this will not be a
        configurable parameter on many implementations";
    }

    leaf resource {
      type string;
      description
        "The item that is under event within the device. The
        resource may be a reference to an item which is
        defined elsewhere in the model. For example, it
        may be a platform/component, interfaces/interface,
        terminal-device/logical-channels/channel, etc. In this
        case the system should match the name of the referenced
        item exactly. The referenced item could alternatively be
        the path of the item within the model.";
    }

    leaf text {
      type string;
      description
        "The string used to inform operators about the event. This
         MUST contain enough information for an operator to be able
         to understand the problem. If this string contains structure,
         this format should be clearly documented for programs to be
         able to parse that information";
    }

    leaf time-created {
      type oc-types:timeticks64;
      description
        "The time at which the event was raised by the system.
        This value is expressed as nanoseconds since the Unix Epoch";
    }

    leaf severity {
      type identityref {
        base oc-alarm-types:OPENCONFIG_ALARM_SEVERITY;
      }
      description
        "The severity level indicating the criticality and impact
        of the event";
    }

    leaf type-id {
      type union {
        type string;
        type identityref {
          base oc-alarm-types:OPENCONFIG_ALARM_TYPE_ID;
        }
      }
      description
        "The abbreviated name of the alarm, for example LOS,
        EQPT, or OTS. Also referred to in different systems as
        condition type, alarm identifier, or alarm mnemonic. It
        is recommended to use the OPENCONFIG_ALARM_TYPE_ID
        identities where possible and only use the string type
        when the desired identityref is not yet defined"; 
    }    

    leaf vendor-type {
      type string;
      description
        "vendor-type leaf in the platform yang model.
        Device model type for the component, defined by the supplier.  
        Where component preconfiguration is supported, for example,
        the component name may be configurable.";
    } 

    leaf event-abbreviate {
      type string;
      description
        "Event abbreviate for this event.";
    }

    leaf hostname {
      type oc-inet:domain-name;
      description
        "The hostname of the device.";
    }
  }

  // notification

  notification event-notification {

    container events {
      uses event-top;
    }
  }
}
