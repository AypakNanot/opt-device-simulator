module "openconfig-platform-mcu" {
  yang-version "1";
  namespace "http://openconfig.net/yang/platform/mcu";
  prefix "oc-mcu";
  import "openconfig-platform" {
    prefix "oc-platform";
  }

  import "openconfig-platform-types" {
    prefix "oc-platform-types";
  }

  import "openconfig-extensions" {
    prefix "oc-ext";
  }

  organization
    " working group";
  contact
    "  working group";
  description
    "This module defines data related to mcu components in
the openconfig-platform model";
  revision "2023-04-26" {
    description
      "Initial release for MinOTN.";
    reference
      "1.0.0";
  }

  grouping "mcu-config" {
    description
      "Configuration data for mcu components";
  }

  grouping "mcu-state" {
    description
      "Operational state data for mcu components";
    leaf "mcu-total-memory" {
      type "uint32";
      units "MB";
      description
        "total memory for mcu components";
    }

    leaf "mcu-available-memory" {
      type "uint32";
      units "MB";
      description
        "Available memory for mcu components";
    }

    leaf "mcu-cpu-utilization" {
      type "uint64";
      description
        "The utilization of Current CPU";
    }

    leaf "active" {
      type "boolean";
      description
        "Active status for mcu components";
    }

  }

  augment "/oc-platform:components/oc-platform:component/oc-platform:mcu/oc-platform:state" {
    description
      "Adding mcu state data";
    uses "mcu-state";
  }

}
