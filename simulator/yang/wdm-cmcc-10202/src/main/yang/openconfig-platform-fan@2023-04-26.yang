module "openconfig-platform-fan" {
  yang-version "1";
  namespace "http://openconfig.net/yang/platform/fan";
  prefix "oc-fan";
  import "openconfig-platform" {
    prefix "oc-platform";
  }

  import "openconfig-extensions" {
    prefix "oc-ext";
  }

  import "openconfig-platform-types" {
    prefix "oc-platform-types";
  }

  organization
    "OpenConfig working group";
  contact
    "OpenConfig working group
www.openconfig.net";
  description
    "This module defines data related to FAN components in the
OpenConfig platform model.";
  revision "2023-04-26" {
    description
      "Initial release for MinOTN.";
    reference
      "0.1.2";
  }

  revision "2018-11-21" {
    description
      "Add OpenConfig module metadata extensions.";
    reference
      "0.1.1";
  }

  revision "2018-01-18" {
    description
      "Initial revision";
    reference
      "0.1.0";
  }

  grouping "fan-config" {
    description
      "Operational config data for fan components";
    leaf "fan-mode" {
      type "oc-platform-types:fan-mode-type";
      description
        "Sets fan mode";
    }

    leaf "fan-speed" {
      type "oc-platform-types:fan-speed-type";
      description
        "Sets fan speed";
    }

    leaf "fan-speed-high-threshold" {
      type "uint32";
      units "rpm";
      description
        "Sets fan speed high threshold";
    }

  }

  grouping "fan-state" {
    description
      "Operational state data for fan components";
  }

  augment "/oc-platform:components/oc-platform:component/oc-platform:fan/oc-platform:config" {
    description
      "Adding fan data to component model";
    uses "fan-config";
  }

  augment "/oc-platform:components/oc-platform:component/oc-platform:fan/oc-platform:state" {
    description
      "Adding fan data to component model";
    uses "fan-config";
    uses "fan-state";
  }

}
